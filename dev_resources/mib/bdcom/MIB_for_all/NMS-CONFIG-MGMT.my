-- *****************************************************************
-- NMS-CONFIG-MGMT.my: MIB for CPU and process statistics
--
-- July 2009
--
-- Copyright (c) 2003 by NMS, Inc.
-- All rights reserved.
-- *****************************************************************
 NMS-CONFIG  DEFINITIONS ::= BEGIN

IMPORTS
	MODULE-IDENTITY,
	OBJECT-TYPE
		FROM SNMPv2-SMI
	nmsWorkGroup
		FROM NMS-SMI;


       linmsm       OBJECT IDENTIFIER ::= { nmsWorkGroup 15 }
       configuration       OBJECT IDENTIFIER ::= { linmsm 1 }


          operation OBJECT-TYPE
              SYNTAX  INTEGER (0..127)
              ACCESS  read-write
              STATUS  mandatory
              DESCRIPTION  "1 means to save the commmand configuration. 2 means to save ifIndex configuration."
             ::= { configuration 1 }

          result OBJECT-TYPE
              SYNTAX  INTEGER (0..127)
              ACCESS  read-only
              STATUS  mandatory
              DESCRIPTION  ""
             ::= { configuration 2 }


END
