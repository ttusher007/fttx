-- *****************************************************************
-- NMS-EPON-PERFORMANCE.MIB:  NMS LLID MIB file
-- AUG 2009
-- *****************************************************************
--

               NMS-EPON-PERFORMANCE DEFINITIONS ::= BEGIN

               IMPORTS
                    Counter, IpAddress, Counter
			FROM RFC1155-SMI
		    OBJECT-TYPE
			FROM RFC-1212
                    DisplayString
			FROM RFC1213-MIB
		    nmsEPONGroup
			FROM NMS-SMI
		    TruthValue,RowStatus,DateAndTime
		    	FROM SNMPv2-TC
		    Counter64 	
		    	FROM SNMPv2-SMI;
          
               nmsEponPerf         OBJECT IDENTIFIER ::= { nmsEPONGroup 202  }
               
               
               nmsEponOltPerfStatGlobalSet OBJECT IDENTIFIER ::= { nmsEponPerf 1  }
               
                perfStat15MinMaxRecord OBJECT-TYPE
                   SYNTAX  INTEGER(1..96)
                   ACCESS  read-write
                   STATUS  mandatory
                   DESCRIPTION
                           "The max record number of 15min performance statistics. The range is 1-96."
                   ::= { nmsEponOltPerfStatGlobalSet 1 } 
              
                perfStat24HourMaxRecord OBJECT-TYPE
                   SYNTAX  INTEGER(1..7)
                   ACCESS  read-write
                   STATUS  mandatory
                   DESCRIPTION
                           "The max record number of 24hour performance statistics. The range is 1-7."
                   ::= { nmsEponOltPerfStatGlobalSet 2 } 
                          

               nmsEponOltPerfStatPortTable OBJECT-TYPE
                   SYNTAX  SEQUENCE OF NmsEponOltPerfStatPortEntry
                   ACCESS  not-accessible
                   STATUS  mandatory
                   DESCRIPTION
                            "A list of epon OLT port performance statistics table entries."
                   ::= { nmsEponPerf 2 }

               nmsEponOltPerfStatPortEntry OBJECT-TYPE
                   SYNTAX NmsEponOltPerfStatPortEntry
                   ACCESS  not-accessible
                   STATUS  mandatory
                   DESCRIPTION
                            "A collection of additional objects in the
                            epon OLT port performance statistics table."
                   INDEX { ifIndex }
               ::= { nmsEponOltPerfStatPortTable 1 }
               
               
               NmsEponOltPerfStatPortEntry ::=
                   SEQUENCE {
                       ifIndex
                           INTEGER,
                       perfStat15MinEnable
                           INTEGER,
                       perfStat24HourEnable
                           INTEGER
		}
		
               ifIndex OBJECT-TYPE
                   SYNTAX  INTEGER
                   ACCESS  read-only
                   STATUS  mandatory
                   DESCRIPTION
                           "The only diid of physical port in System, including NNI port and EPON port."
                   ::= { nmsEponOltPerfStatPortEntry 1 } 
			
               perfStat15MinEnable OBJECT-TYPE
                   SYNTAX  INTEGER{
                                    enable(1),
                                    disable(2)
                                   }
                   ACCESS  read-write
                   STATUS  mandatory
                   DESCRIPTION
                           "Enable 15 minute performance statistics"
                   ::= { nmsEponOltPerfStatPortEntry 2 } 
		
               perfStat24HourEnable OBJECT-TYPE
                   SYNTAX  INTEGER{
                                    enable(1),
                                    disable(2)
                                   }
                   ACCESS  read-write
                   STATUS  mandatory
                   DESCRIPTION
                           "Enable 24 hour performance statistics"
                   ::= { nmsEponOltPerfStatPortEntry 3 } 
		
		
		
               nmsEponOltPerfStat15MinTable OBJECT-TYPE
                   SYNTAX  SEQUENCE OF NmsEponOltPerfStat15MinEntry
                   ACCESS  not-accessible
                   STATUS  mandatory
                   DESCRIPTION
                            "A list of epon OLT port 15 minute performance statistics table entries."
                   ::= { nmsEponPerf 3 }

               nmsEponOltPerfStat15MinEntry OBJECT-TYPE
                   SYNTAX NmsEponOltPerfStat15MinEntry
                   ACCESS  not-accessible
                   STATUS  mandatory
                   DESCRIPTION
                            "A collection of additional objects in the
                            epon OLT port 15 minute performance statistics table."
                   INDEX { ifIndex15Min }
               ::= { nmsEponOltPerfStat15MinTable 1 }
               
              NmsEponOltPerfStat15MinEntry ::=
                   SEQUENCE {
                       ifIndex15Min
                           INTEGER,
                       stats15Index
                           INTEGER,
                       stats15StatusAndAction
                           INTEGER,
                       stats15EndTime
                           DateAndTime,
                       stats15InOctets
                           Counter64,
                       stats15InPkts
                           Counter64,
                       stats15InBroadcastPkts
                           Counter64,
                       stats15InMulticastPkts
                           Counter64,
                       stats15InPkts64Octets
                           Counter64,
                       stats15InPkts65to127Octets
                           Counter64,
                       stats15InPkts128to255Octets
                           Counter64,
                       stats15InPkts256to511Octets
                           Counter64,
                       stats15InPkts512to1023Octets
                           Counter64,
                       stats15InPkts1024to1518Octets
                           Counter64,
                       stats15InUndersizePks
                           Counter64,
                       stats15InOversizePks
                           Counter64,
                       stats15InFragments
                           Counter64,
                       stats15InMpcpFrames
                           Counter64,
                       stats15InOAMFrames
                           Counter64,
                       stats15InCRCErrorPkts
                           Counter64,
                       stats15InDiscardPkts
                           Counter64,
                       stats15InJabbers
                           Counter64,
                       stats15OutOctets
                           Counter64,
                       stats15OutPkts
                           Counter64,
                       stats15OutBroadcastPkts
                           Counter64,
                       stats15OutMulticastPkts
                           Counter64,
                       stats15OutPkts64Octets
                           Counter64,
                       stats15OutPkts65to127Octets
                           Counter64,
                       stats15OutPkts128to255Octets
                           Counter64,
                       stats15OutPkts256to511Octets
                           Counter64,
                       stats15OutPkts512to1023Octets
                           Counter64,
                       stats15OutPkts1024to1518Octets
                           Counter64,
                       stats15OutOversizePks
                           Counter64,
                       stats15OutMpcpFrames
                           Counter64,
                       stats15OutOAMFrames
                           Counter64,
                       stats15OutDiscardPktsx
                           Counter64
		}
		
               ifIndex15Min OBJECT-TYPE
                   SYNTAX  INTEGER
                   ACCESS  read-only
                   STATUS  mandatory
                   DESCRIPTION
                           "The only diid of physical port in System, including NNI port and EPON port."
                   ::= { nmsEponOltPerfStat15MinEntry 1 } 
			
               stats15Index OBJECT-TYPE
                   SYNTAX  INTEGER
                   ACCESS  read-only
                   STATUS  mandatory
                   DESCRIPTION
                           "Statistics record index."
                   ::= { nmsEponOltPerfStat15MinEntry 2 } 

			
               stats15StatusAndAction OBJECT-TYPE
                   SYNTAX  INTEGER{
                   		   none(1),
                   		   clean(2)
                                   }
                   ACCESS  read-write
                   STATUS  mandatory
                   DESCRIPTION
                           "Status and action of current statistics record."
                   ::= { nmsEponOltPerfStat15MinEntry 3 } 

               stats15EndTime OBJECT-TYPE
                   SYNTAX  DateAndTime
                   ACCESS  read-only
                   STATUS  mandatory
                   DESCRIPTION
                           "End time of the statistics record."
                   ::= { nmsEponOltPerfStat15MinEntry 4 } 

               stats15InOctets OBJECT-TYPE
                   SYNTAX  Counter64
                   ACCESS  read-only
                   STATUS  mandatory
                   DESCRIPTION
                           ""
                   ::= { nmsEponOltPerfStat15MinEntry 5 } 

               stats15InPkts OBJECT-TYPE
                   SYNTAX  Counter64
                   ACCESS  read-only
                   STATUS  mandatory
                   DESCRIPTION
                           ""
                   ::= { nmsEponOltPerfStat15MinEntry 6 } 
                   
               stats15InBroadcastPkts OBJECT-TYPE
                   SYNTAX  Counter64
                   ACCESS  read-only
                   STATUS  mandatory
                   DESCRIPTION
                           ""
                   ::= { nmsEponOltPerfStat15MinEntry 7 } 
                   
               stats15InMulticastPkts OBJECT-TYPE
                   SYNTAX  Counter64
                   ACCESS  read-only
                   STATUS  mandatory
                   DESCRIPTION
                           ""
                   ::= { nmsEponOltPerfStat15MinEntry 8 } 
                   
               stats15InPkts64Octets OBJECT-TYPE
                   SYNTAX  Counter64
                   ACCESS  read-only
                   STATUS  mandatory
                   DESCRIPTION
                           ""
                   ::= { nmsEponOltPerfStat15MinEntry 9 } 
                   
               stats15InPkts65to127Octets OBJECT-TYPE
                   SYNTAX  Counter64
                   ACCESS  read-only
                   STATUS  mandatory
                   DESCRIPTION
                           ""
                   ::= { nmsEponOltPerfStat15MinEntry 10 } 
                   
               stats15InPkts128to255Octets OBJECT-TYPE
                   SYNTAX  Counter64
                   ACCESS  read-only
                   STATUS  mandatory
                   DESCRIPTION
                           ""
                   ::= { nmsEponOltPerfStat15MinEntry 11 } 
                   
               stats15InPkts256to511Octets OBJECT-TYPE
                   SYNTAX  Counter64
                   ACCESS  read-only
                   STATUS  mandatory
                   DESCRIPTION
                           ""
                   ::= { nmsEponOltPerfStat15MinEntry 12 } 
                   
               stats15InPkts512to1023Octets OBJECT-TYPE
                   SYNTAX  Counter64
                   ACCESS  read-only
                   STATUS  mandatory
                   DESCRIPTION
                           ""
                   ::= { nmsEponOltPerfStat15MinEntry 13 } 
                   
                stats15InPkts1024to1518Octets OBJECT-TYPE
                   SYNTAX  Counter64
                   ACCESS  read-only
                   STATUS  mandatory
                   DESCRIPTION
                           ""
                   ::= { nmsEponOltPerfStat15MinEntry 14 } 
                   
                stats15InUndersizePks OBJECT-TYPE
                   SYNTAX  Counter64
                   ACCESS  read-only
                   STATUS  mandatory
                   DESCRIPTION
                           ""
                   ::= { nmsEponOltPerfStat15MinEntry 15 } 
                   
                stats15InOversizePks OBJECT-TYPE
                   SYNTAX  Counter64
                   ACCESS  read-only
                   STATUS  mandatory
                   DESCRIPTION
                           ""
                   ::= { nmsEponOltPerfStat15MinEntry 16 } 
                   
                stats15InFragments OBJECT-TYPE
                   SYNTAX  Counter64
                   ACCESS  read-only
                   STATUS  mandatory
                   DESCRIPTION
                           ""
                   ::= { nmsEponOltPerfStat15MinEntry 17 } 
                   
                stats15InMpcpFrames OBJECT-TYPE
                   SYNTAX  Counter64
                   ACCESS  read-only
                   STATUS  mandatory
                   DESCRIPTION
                           ""
                   ::= { nmsEponOltPerfStat15MinEntry 18 } 
                   
                stats15InOAMFrames OBJECT-TYPE
                   SYNTAX  Counter64
                   ACCESS  read-only
                   STATUS  mandatory
                   DESCRIPTION
                           ""
                   ::= { nmsEponOltPerfStat15MinEntry 19 } 
                   
                stats15InCRCErrorPkts OBJECT-TYPE
                   SYNTAX  Counter64
                   ACCESS  read-only
                   STATUS  mandatory
                   DESCRIPTION
                           ""
                   ::= { nmsEponOltPerfStat15MinEntry 20 } 
                   
                stats15InDiscardPkts OBJECT-TYPE
                   SYNTAX  Counter64
                   ACCESS  read-only
                   STATUS  mandatory
                   DESCRIPTION
                           ""
                   ::= { nmsEponOltPerfStat15MinEntry 21 } 
                   
                stats15InJabbers OBJECT-TYPE
                   SYNTAX  Counter64
                   ACCESS  read-only
                   STATUS  mandatory
                   DESCRIPTION
                           ""
                   ::= { nmsEponOltPerfStat15MinEntry 22 } 
                   
                stats15OutOctets OBJECT-TYPE
                   SYNTAX  Counter64
                   ACCESS  read-only
                   STATUS  mandatory
                   DESCRIPTION
                           ""
                   ::= { nmsEponOltPerfStat15MinEntry 23 } 
                   
                stats15OutPkts OBJECT-TYPE
                   SYNTAX  Counter64
                   ACCESS  read-only
                   STATUS  mandatory
                   DESCRIPTION
                           ""
                   ::= { nmsEponOltPerfStat15MinEntry 24 } 
                   
                stats15OutBroadcastPkts OBJECT-TYPE
                   SYNTAX  Counter64
                   ACCESS  read-only
                   STATUS  mandatory
                   DESCRIPTION
                           ""
                   ::= { nmsEponOltPerfStat15MinEntry 25 } 
                   
                stats15OutMulticastPkts OBJECT-TYPE
                   SYNTAX  Counter64
                   ACCESS  read-only
                   STATUS  mandatory
                   DESCRIPTION
                           ""
                   ::= { nmsEponOltPerfStat15MinEntry 26 } 
                   
                stats15OutPkts64Octets OBJECT-TYPE
                   SYNTAX  Counter64
                   ACCESS  read-only
                   STATUS  mandatory
                   DESCRIPTION
                           ""
                   ::= { nmsEponOltPerfStat15MinEntry 27 } 
                   
                stats15OutPkts65to127Octets OBJECT-TYPE
                   SYNTAX  Counter64
                   ACCESS  read-only
                   STATUS  mandatory
                   DESCRIPTION
                           ""
                   ::= { nmsEponOltPerfStat15MinEntry 28 } 
                   
                stats15OutPkts128to255Octets OBJECT-TYPE
                   SYNTAX  Counter64
                   ACCESS  read-only
                   STATUS  mandatory
                   DESCRIPTION
                           ""
                   ::= { nmsEponOltPerfStat15MinEntry 29 } 
                   
                stats15OutPkts256to511Octets OBJECT-TYPE
                   SYNTAX  Counter64
                   ACCESS  read-only
                   STATUS  mandatory
                   DESCRIPTION
                           ""
                   ::= { nmsEponOltPerfStat15MinEntry 30 } 
                   
                stats15OutPkts512to1023Octets OBJECT-TYPE
                   SYNTAX  Counter64
                   ACCESS  read-only
                   STATUS  mandatory
                   DESCRIPTION
                           ""
                   ::= { nmsEponOltPerfStat15MinEntry 31 } 
                   
                stats15OutPkts1024to1518Octets OBJECT-TYPE
                   SYNTAX  Counter64
                   ACCESS  read-only
                   STATUS  mandatory
                   DESCRIPTION
                           ""
                   ::= { nmsEponOltPerfStat15MinEntry 32 } 
                   
                stats15OutOversizePks OBJECT-TYPE
                   SYNTAX  Counter64
                   ACCESS  read-only
                   STATUS  mandatory
                   DESCRIPTION
                           ""
                   ::= { nmsEponOltPerfStat15MinEntry 33 } 
                   
                stats15OutMpcpFrames OBJECT-TYPE
                   SYNTAX  Counter64
                   ACCESS  read-only
                   STATUS  mandatory
                   DESCRIPTION
                           ""
                   ::= { nmsEponOltPerfStat15MinEntry 34 } 
                   
                stats15OutOAMFrames OBJECT-TYPE
                   SYNTAX  Counter64
                   ACCESS  read-only
                   STATUS  mandatory
                   DESCRIPTION
                           ""
                   ::= { nmsEponOltPerfStat15MinEntry 35 } 
                   
                stats15OutDiscardPktsx OBJECT-TYPE
                   SYNTAX  Counter64
                   ACCESS  read-only
                   STATUS  mandatory
                   DESCRIPTION
                           ""
                   ::= { nmsEponOltPerfStat15MinEntry 36 } 
                       
		
               nmsEponOltPerfStat24HourTable OBJECT-TYPE
                   SYNTAX  SEQUENCE OF NmsEponOltPerfStat24HourEntry
                   ACCESS  not-accessible
                   STATUS  mandatory
                   DESCRIPTION
                            "A list of epon OLT port 24 hour performance statistics table entries."
                   ::= { nmsEponPerf 4 }

               nmsEponOltPerfStat24HourEntry OBJECT-TYPE
                   SYNTAX NmsEponOltPerfStat24HourEntry
                   ACCESS  not-accessible
                   STATUS  mandatory
                   DESCRIPTION
                            "A collection of additional objects in the
                            epon OLT port 24 hour performance statistics table."
                   INDEX { ifIndex24Hour }
               ::= { nmsEponOltPerfStat24HourTable 1 }
		
              NmsEponOltPerfStat24HourEntry ::=
                   SEQUENCE {
                       ifIndex24Hour
                           INTEGER,
                       stats24Index
                           INTEGER,
                       stats24StatusAndAction
                           INTEGER,
                       stats24EndTime
                           DateAndTime,
                       stats24InOctets
                           Counter64,
                       stats24InPkts
                           Counter64,
                       stats24InBroadcastPkts
                           Counter64,
                       stats24InMulticastPkts
                           Counter64,
                       stats24InPkts64Octets
                           Counter64,
                       stats24InPkts65to127Octets
                           Counter64,
                       stats24InPkts128to255Octets
                           Counter64,
                       stats24InPkts256to511Octets
                           Counter64,
                       stats24InPkts512to1023Octets
                           Counter64,
                       stats24InPkts1024to1518Octets
                           Counter64,
                       stats24InUndersizePks
                           Counter64,
                       stats24InOversizePks
                           Counter64,
                       stats24InFragments
                           Counter64,
                       stats24InMpcpFrames
                           Counter64,
                       stats24InOAMFrames
                           Counter64,
                       stats24InCRCErrorPkts
                           Counter64,
                       stats24InDiscardPkts
                           Counter64,
                       stats24InJabbers
                           Counter64,
                       stats24OutOctets
                           Counter64,
                       stats24OutPkts
                           Counter64,
                       stats24OutBroadcastPkts
                           Counter64,
                       stats24OutMulticastPkts
                           Counter64,
                       stats24OutPkts64Octets
                           Counter64,
                       stats24OutPkts65to127Octets
                           Counter64,
                       stats24OutPkts128to255Octets
                           Counter64,
                       stats24OutPkts256to511Octets
                           Counter64,
                       stats24OutPkts512to1023Octets
                           Counter64,
                       stats24OutPkts1024to1518Octets
                           Counter64,
                       stats24OutOversizePks
                           Counter64,
                       stats24OutMpcpFrames
                           Counter64,
                       stats24OutOAMFrames
                           Counter64,
                       stats24OutDiscardPktsx
                           Counter64
		}
		
               ifIndex24Hour OBJECT-TYPE
                   SYNTAX  INTEGER
                   ACCESS  read-only
                   STATUS  mandatory
                   DESCRIPTION
                           "The only diid of physical port in System, including NNI port and EPON port."
                   ::= { nmsEponOltPerfStat24HourEntry 1 } 
			
               stats24Index OBJECT-TYPE
                   SYNTAX  INTEGER
                   ACCESS  read-only
                   STATUS  mandatory
                   DESCRIPTION
                           "Statistics record index."
                   ::= { nmsEponOltPerfStat24HourEntry 2 } 

			
               stats24StatusAndAction OBJECT-TYPE
                   SYNTAX  INTEGER{
                   		   none(1),
                   		   clean(2)
                                   }
                   ACCESS  read-write
                   STATUS  mandatory
                   DESCRIPTION
                           "Status and action of current statistics record."
                   ::= { nmsEponOltPerfStat24HourEntry 3 } 

               stats24EndTime OBJECT-TYPE
                   SYNTAX  DateAndTime
                   ACCESS  read-only
                   STATUS  mandatory
                   DESCRIPTION
                           "End time of the statistics record."
                   ::= { nmsEponOltPerfStat24HourEntry 4 } 

               stats24InOctets OBJECT-TYPE
                   SYNTAX  Counter64
                   ACCESS  read-only
                   STATUS  mandatory
                   DESCRIPTION
                           ""
                   ::= { nmsEponOltPerfStat24HourEntry 5 } 

               stats24InPkts OBJECT-TYPE
                   SYNTAX  Counter64
                   ACCESS  read-only
                   STATUS  mandatory
                   DESCRIPTION
                           ""
                   ::= { nmsEponOltPerfStat24HourEntry 6 } 
                   
               stats24InBroadcastPkts OBJECT-TYPE
                   SYNTAX  Counter64
                   ACCESS  read-only
                   STATUS  mandatory
                   DESCRIPTION
                           ""
                   ::= { nmsEponOltPerfStat24HourEntry 7 } 
                   
               stats24InMulticastPkts OBJECT-TYPE
                   SYNTAX  Counter64
                   ACCESS  read-only
                   STATUS  mandatory
                   DESCRIPTION
                           ""
                   ::= { nmsEponOltPerfStat24HourEntry 8 } 
                   
               stats24InPkts64Octets OBJECT-TYPE
                   SYNTAX  Counter64
                   ACCESS  read-only
                   STATUS  mandatory
                   DESCRIPTION
                           ""
                   ::= { nmsEponOltPerfStat24HourEntry 9 } 
                   
               stats24InPkts65to127Octets OBJECT-TYPE
                   SYNTAX  Counter64
                   ACCESS  read-only
                   STATUS  mandatory
                   DESCRIPTION
                           ""
                   ::= { nmsEponOltPerfStat24HourEntry 10 } 
                   
               stats24InPkts128to255Octets OBJECT-TYPE
                   SYNTAX  Counter64
                   ACCESS  read-only
                   STATUS  mandatory
                   DESCRIPTION
                           ""
                   ::= { nmsEponOltPerfStat24HourEntry 11 } 
                   
               stats24InPkts256to511Octets OBJECT-TYPE
                   SYNTAX  Counter64
                   ACCESS  read-only
                   STATUS  mandatory
                   DESCRIPTION
                           ""
                   ::= { nmsEponOltPerfStat24HourEntry 12 } 
                   
               stats24InPkts512to1023Octets OBJECT-TYPE
                   SYNTAX  Counter64
                   ACCESS  read-only
                   STATUS  mandatory
                   DESCRIPTION
                           ""
                   ::= { nmsEponOltPerfStat24HourEntry 13 } 
                   
                stats24InPkts1024to1518Octets OBJECT-TYPE
                   SYNTAX  Counter64
                   ACCESS  read-only
                   STATUS  mandatory
                   DESCRIPTION
                           ""
                   ::= { nmsEponOltPerfStat24HourEntry 14 } 
                   
                stats24InUndersizePks OBJECT-TYPE
                   SYNTAX  Counter64
                   ACCESS  read-only
                   STATUS  mandatory
                   DESCRIPTION
                           ""
                   ::= { nmsEponOltPerfStat24HourEntry 15 } 
                   
                stats24InOversizePks OBJECT-TYPE
                   SYNTAX  Counter64
                   ACCESS  read-only
                   STATUS  mandatory
                   DESCRIPTION
                           ""
                   ::= { nmsEponOltPerfStat24HourEntry 16 } 
                   
                stats24InFragments OBJECT-TYPE
                   SYNTAX  Counter64
                   ACCESS  read-only
                   STATUS  mandatory
                   DESCRIPTION
                           ""
                   ::= { nmsEponOltPerfStat24HourEntry 17 } 
                   
                stats24InMpcpFrames OBJECT-TYPE
                   SYNTAX  Counter64
                   ACCESS  read-only
                   STATUS  mandatory
                   DESCRIPTION
                           ""
                   ::= { nmsEponOltPerfStat24HourEntry 18 } 
                   
                stats24InOAMFrames OBJECT-TYPE
                   SYNTAX  Counter64
                   ACCESS  read-only
                   STATUS  mandatory
                   DESCRIPTION
                           ""
                   ::= { nmsEponOltPerfStat24HourEntry 19 } 
                   
                stats24InCRCErrorPkts OBJECT-TYPE
                   SYNTAX  Counter64
                   ACCESS  read-only
                   STATUS  mandatory
                   DESCRIPTION
                           ""
                   ::= { nmsEponOltPerfStat24HourEntry 20 } 
                   
                stats24InDiscardPkts OBJECT-TYPE
                   SYNTAX  Counter64
                   ACCESS  read-only
                   STATUS  mandatory
                   DESCRIPTION
                           ""
                   ::= { nmsEponOltPerfStat24HourEntry 21 } 
                   
                stats24InJabbers OBJECT-TYPE
                   SYNTAX  Counter64
                   ACCESS  read-only
                   STATUS  mandatory
                   DESCRIPTION
                           ""
                   ::= { nmsEponOltPerfStat24HourEntry 22 } 
                   
                stats24OutOctets OBJECT-TYPE
                   SYNTAX  Counter64
                   ACCESS  read-only
                   STATUS  mandatory
                   DESCRIPTION
                           ""
                   ::= { nmsEponOltPerfStat24HourEntry 23 } 
                   
                stats24OutPkts OBJECT-TYPE
                   SYNTAX  Counter64
                   ACCESS  read-only
                   STATUS  mandatory
                   DESCRIPTION
                           ""
                   ::= { nmsEponOltPerfStat24HourEntry 24 } 
                   
                stats24OutBroadcastPkts OBJECT-TYPE
                   SYNTAX  Counter64
                   ACCESS  read-only
                   STATUS  mandatory
                   DESCRIPTION
                           ""
                   ::= { nmsEponOltPerfStat24HourEntry 25 } 
                   
                stats24OutMulticastPkts OBJECT-TYPE
                   SYNTAX  Counter64
                   ACCESS  read-only
                   STATUS  mandatory
                   DESCRIPTION
                           ""
                   ::= { nmsEponOltPerfStat24HourEntry 26 } 
                   
                stats24OutPkts64Octets OBJECT-TYPE
                   SYNTAX  Counter64
                   ACCESS  read-only
                   STATUS  mandatory
                   DESCRIPTION
                           ""
                   ::= { nmsEponOltPerfStat24HourEntry 27 } 
                   
                stats24OutPkts65to127Octets OBJECT-TYPE
                   SYNTAX  Counter64
                   ACCESS  read-only
                   STATUS  mandatory
                   DESCRIPTION
                           ""
                   ::= { nmsEponOltPerfStat24HourEntry 28 } 
                   
                stats24OutPkts128to255Octets OBJECT-TYPE
                   SYNTAX  Counter64
                   ACCESS  read-only
                   STATUS  mandatory
                   DESCRIPTION
                           ""
                   ::= { nmsEponOltPerfStat24HourEntry 29 } 
                   
                stats24OutPkts256to511Octets OBJECT-TYPE
                   SYNTAX  Counter64
                   ACCESS  read-only
                   STATUS  mandatory
                   DESCRIPTION
                           ""
                   ::= { nmsEponOltPerfStat24HourEntry 30 } 
                   
                stats24OutPkts512to1023Octets OBJECT-TYPE
                   SYNTAX  Counter64
                   ACCESS  read-only
                   STATUS  mandatory
                   DESCRIPTION
                           ""
                   ::= { nmsEponOltPerfStat24HourEntry 31 } 
                   
                stats24OutPkts1024to1518Octets OBJECT-TYPE
                   SYNTAX  Counter64
                   ACCESS  read-only
                   STATUS  mandatory
                   DESCRIPTION
                           ""
                   ::= { nmsEponOltPerfStat24HourEntry 32 } 
                   
                stats24OutOversizePks OBJECT-TYPE
                   SYNTAX  Counter64
                   ACCESS  read-only
                   STATUS  mandatory
                   DESCRIPTION
                           ""
                   ::= { nmsEponOltPerfStat24HourEntry 33 } 
                   
                stats24OutMpcpFrames OBJECT-TYPE
                   SYNTAX  Counter64
                   ACCESS  read-only
                   STATUS  mandatory
                   DESCRIPTION
                           ""
                   ::= { nmsEponOltPerfStat24HourEntry 34 } 
                   
                stats24OutOAMFrames OBJECT-TYPE
                   SYNTAX  Counter64
                   ACCESS  read-only
                   STATUS  mandatory
                   DESCRIPTION
                           ""
                   ::= { nmsEponOltPerfStat24HourEntry 35 } 
                   
                stats24OutDiscardPktsx OBJECT-TYPE
                   SYNTAX  Counter64
                   ACCESS  read-only
                   STATUS  mandatory
                   DESCRIPTION
                           ""
                   ::= { nmsEponOltPerfStat24HourEntry 36 } 
                       

               

			
END
