--
-- 
-- MIB generated by MG-SOFT Visual MIB Builder Version 6.0  Build 88
-- Friday, September 12, 2014 at 18:02:11
--

	NMS-EPON-OLT-PERFORMANCE DEFINITIONS ::= BEGIN
 
		IMPORTS
			OBJECT-TYPE			
				FROM RFC-1212			
			TRAP-TYPE			
				FROM RFC-1215
			nmsEPONGroup				
			        FROM NMS-SMI
			RowStatus
			    	FROM SNMPv2-TC
			nmsEponOnuTrap 
			        FROM NMS-EPON-ONU-TRAP  ;
	
	
--
-- Node definitions
--



	
		-- 1
		nmsOnuPerf OBJECT IDENTIFIER ::= {nmsEPONGroup  201 }

		
		-- 1.1
		nmsOnuPerfSet OBJECT IDENTIFIER ::= { nmsOnuPerf 1 }

		
		-- 1.1.1
		onuPerformParameterAlarmsSetTable OBJECT-TYPE
			SYNTAX SEQUENCE OF OnuPerformParameterAlarmsSetEntry
			ACCESS not-accessible
			STATUS mandatory
			DESCRIPTION
				"Description."
			::= { nmsOnuPerfSet 1 }

		
		-- 1.1.1.1
		onuPerformParameterAlarmsSetEntry OBJECT-TYPE
			SYNTAX OnuPerformParameterAlarmsSetEntry
			ACCESS not-accessible
			STATUS mandatory
			DESCRIPTION
				"Description."
			INDEX { llidIfIndex }
			::= { onuPerformParameterAlarmsSetTable 1 }

		
		OnuPerformParameterAlarmsSetEntry ::=
			SEQUENCE { 
				llidIfIndex
					INTEGER,
				cpuUsageHighLimitEnable
					INTEGER,
				cpuUsageHighLimitThreshold
					INTEGER,
				cpuUsageHighLimitClearThreshold
					INTEGER,
				cpuUsageHighLimitRowStatus
					RowStatus,
				ramUsageHighLimitEnable
					INTEGER,
				ramUsageHighLimitThreshold
					INTEGER,
				ramUsageHighLimitClearThreshold
					INTEGER,
				ramUsageHighLimitRowStatus
					RowStatus,
				temperatureAlarmUpLimitEnable
					INTEGER,
				temperatureAlarmUpLimitThreshold
					INTEGER,
				temperatureAlarmUpLimitClearThreshold
					INTEGER,
				temperatureAlarmUpLimitRowStatus
					RowStatus,
				temperatureAlarmLowLimitEnable
					INTEGER,
				temperatureAlarmLowLimitThreshold
					INTEGER,
				temperatureAlarmLowLimitClearThreshold
					INTEGER,
				temperatureAlarmLowLimitRowStatus
					RowStatus,
				voltageAlarmUpLimitEnable
					INTEGER,
				voltageAlarmUpLimitThreshold
					INTEGER,
				voltageAlarmUpLimitClearThreshold
					INTEGER,
				voltageAlarmUpLimitRowStatus
					RowStatus,
				voltageAlarmLowLimitEnable
					INTEGER,
				voltageAlarmLowLimitThreshold
					INTEGER,
				voltageAlarmLowLimitClearThreshold
					INTEGER,
				voltageAlarmLowLimitRowStatus
					RowStatus
			 }

		-- 1.1.1.1.1
		llidIfIndex OBJECT-TYPE
			SYNTAX INTEGER 
			ACCESS read-only
			STATUS mandatory
			DESCRIPTION
				"Index of LLID interface."
			::= { onuPerformParameterAlarmsSetEntry 1 }

		
		-- 1.1.1.1.2
		cpuUsageHighLimitEnable OBJECT-TYPE
			SYNTAX INTEGER
				{
				enable(1),
				disable(2)
				}
			ACCESS read-write
			STATUS mandatory
			DESCRIPTION
				"Enable or disable the alarm of CPU usage. 1-enable, 2-disable. Default is disable."
			::= { onuPerformParameterAlarmsSetEntry 2 }

		
		-- 1.1.1.1.3
		cpuUsageHighLimitThreshold OBJECT-TYPE
			SYNTAX INTEGER(1..100)
			ACCESS read-write
			STATUS mandatory
			DESCRIPTION
				"The upper threshold of CPU usage alarm. The unit is 1%. The range is 1-100. Default is 100."
			::= { onuPerformParameterAlarmsSetEntry 3 }

		
		-- 1.1.1.1.4
		cpuUsageHighLimitClearThreshold OBJECT-TYPE
			SYNTAX INTEGER(1..100)
			ACCESS read-write
			STATUS mandatory
			DESCRIPTION
				"The upper threshold  of CPU usage alarm cleared. The range is 1-100. Default is 100."
			::= { onuPerformParameterAlarmsSetEntry 4 }

		
		-- 1.1.1.1.5
		cpuUsageHighLimitRowStatus OBJECT-TYPE
			SYNTAX RowStatus
			ACCESS read-create
			STATUS mandatory
			DESCRIPTION
				"The row status of CPU usage alarm ."
			::= { onuPerformParameterAlarmsSetEntry 5 }

		
		-- 1.1.1.1.6
		ramUsageHighLimitEnable OBJECT-TYPE
			SYNTAX INTEGER
				{
				enable(1),
				disable(2)
				}
			ACCESS read-write
			STATUS mandatory
			DESCRIPTION
				"Enable or disable the alarm of RAM usage. 1-enable, 2-disable. Default is disable."
			::= { onuPerformParameterAlarmsSetEntry 6 }

		
		-- 1.1.1.1.7
		ramUsageHighLimitThreshold OBJECT-TYPE
			SYNTAX INTEGER(1..100)
			ACCESS read-write
			STATUS mandatory
			DESCRIPTION
				"The upper threshold of RAM usage alarm. The unit is 1%. The range is 1-100. Default is 100."
			::= { onuPerformParameterAlarmsSetEntry 7 }

		
		-- 1.1.1.1.8
		ramUsageHighLimitClearThreshold OBJECT-TYPE
			SYNTAX INTEGER(1..100)
			ACCESS read-write
			STATUS mandatory
			DESCRIPTION
				"The upper threshold  of RAM usage alarm cleared. The range is 1-100. Default is 100."
			::= { onuPerformParameterAlarmsSetEntry 8 }

		
		-- 1.1.1.1.9
		ramUsageHighLimitRowStatus OBJECT-TYPE
			SYNTAX RowStatus
			ACCESS read-create
			STATUS mandatory
			DESCRIPTION
				"The row status of RAM usage alarm ."
			::= { onuPerformParameterAlarmsSetEntry 9 }

		
		-- 1.1.1.1.10
		temperatureAlarmUpLimitEnable OBJECT-TYPE
			SYNTAX INTEGER {
			                 enable(1),
			                 disable(2)
			                }
			ACCESS read-write
			STATUS mandatory
			DESCRIPTION
				"Enable or disable the alarm of PON high temperature. 1-enable, 2-disable. Default is disable."
			::= { onuPerformParameterAlarmsSetEntry 10 }

		
		-- 1.1.1.1.11
		temperatureAlarmUpLimitThreshold OBJECT-TYPE
			SYNTAX INTEGER(-1280..1280)
			ACCESS read-write
			STATUS mandatory
			DESCRIPTION
				"The upper threshold of temperature alarm. The unit is 0.1 degree. The range is -1280-1280. Default is 1280."
			::= { onuPerformParameterAlarmsSetEntry 11 }

		
		-- 1.1.1.1.12
		temperatureAlarmUpLimitClearThreshold OBJECT-TYPE
			SYNTAX INTEGER(-1280..1280)
			ACCESS read-write
			STATUS mandatory
			DESCRIPTION
				"The upper threshold temperature alarm cleared. The unit is 0.1 degree. The range is -1280-1280. Default is 1280."
			::= { onuPerformParameterAlarmsSetEntry 12 }

		
		-- 1.1.1.1.13
		temperatureAlarmUpLimitRowStatus OBJECT-TYPE
			SYNTAX RowStatus
			ACCESS read-create
			STATUS mandatory
			DESCRIPTION
				"The row status of temperature upper alarm."
			::= { onuPerformParameterAlarmsSetEntry 13 }

		
		-- 1.1.1.1.14
		temperatureAlarmLowLimitEnable OBJECT-TYPE
			SYNTAX INTEGER
				{
				enable(1),
				disable(2)
				}
			ACCESS read-write
			STATUS mandatory
			DESCRIPTION
				"Enable or disable the alarm of PON low temperature. 1-enable, 2-disable. Default is disable."
			::= { onuPerformParameterAlarmsSetEntry 14 }

		
		-- 1.1.1.1.15
		temperatureAlarmLowLimitThreshold OBJECT-TYPE
			SYNTAX INTEGER(-1280..1280)
			ACCESS read-write
			STATUS mandatory
			DESCRIPTION
				"The low threshold of temperature alarm. The unit is 0.1 degree. The range is -1280-1280. Default is -1280."
			::= { onuPerformParameterAlarmsSetEntry 15 }

		
		-- 1.1.1.1.16
		temperatureAlarmLowLimitClearThreshold OBJECT-TYPE
			SYNTAX INTEGER(-1280..1280)
			ACCESS read-write
			STATUS mandatory
			DESCRIPTION
				"The low threshold temperature alarm cleared. The unit is 0.1 degree. The range is -1280-1280. Default is -1280."
			::= { onuPerformParameterAlarmsSetEntry 16 }

		
		-- 1.1.1.1.17
		temperatureAlarmLowLimitRowStatus OBJECT-TYPE
			SYNTAX RowStatus
			ACCESS read-create
			STATUS mandatory
			DESCRIPTION
				"The row status of temperature low alarm."
			::= { onuPerformParameterAlarmsSetEntry 17 }

		
		-- 1.1.1.1.18
		voltageAlarmUpLimitEnable OBJECT-TYPE
			SYNTAX INTEGER
				{
				enable(1),
				disable(2)
				}
			ACCESS read-write
			STATUS mandatory
			DESCRIPTION
				"Enable or disable the alarm of PON high voltage. 1-enable, 2-disable. Default is disable."
			::= { onuPerformParameterAlarmsSetEntry 18 }

		
		-- 1.1.1.1.19
		voltageAlarmUpLimitThreshold OBJECT-TYPE
			SYNTAX INTEGER(0..65)
			ACCESS read-write
			STATUS mandatory
			DESCRIPTION
				"The upper threshold of voltage alarm. The unit is 0.1V. The range is 0-65. Default is 65."
			::= { onuPerformParameterAlarmsSetEntry 19 }

		
		-- 1.1.1.1.20
		voltageAlarmUpLimitClearThreshold OBJECT-TYPE
			SYNTAX INTEGER(0..65)
			ACCESS read-write
			STATUS mandatory
			DESCRIPTION
				"The upper threshold voltage alarm cleared. The unit is 0.1V. The range is 0-65. Default is 65."
			::= { onuPerformParameterAlarmsSetEntry 20 }

		
		-- 1.1.1.1.21
		voltageAlarmUpLimitRowStatus OBJECT-TYPE
			SYNTAX RowStatus
			ACCESS read-create
			STATUS mandatory
			DESCRIPTION
				"The row status of voltage upper alarm."
			::= { onuPerformParameterAlarmsSetEntry 21 }

		
		-- 1.1.1.1.22
		voltageAlarmLowLimitEnable OBJECT-TYPE
			SYNTAX INTEGER
				{
				enable(1),
				disable(2)
				}
			ACCESS read-write
			STATUS mandatory
			DESCRIPTION
				"Enable or disable the alarm of PON low voltage. 1-enable, 2-disable. Default is disable."
			::= { onuPerformParameterAlarmsSetEntry 22 }

		
		-- 1.1.1.1.23
		voltageAlarmLowLimitThreshold OBJECT-TYPE
			SYNTAX INTEGER(0..65)
			ACCESS read-write
			STATUS mandatory
			DESCRIPTION
				"The low threshold of voltage alarm. The unit is 0.1V. The range is 0-65. Default is 0."
			::= { onuPerformParameterAlarmsSetEntry 23 }

		
		-- 1.1.1.1.24
		voltageAlarmLowLimitClearThreshold OBJECT-TYPE
			SYNTAX INTEGER(0..65)
			ACCESS read-write
			STATUS mandatory
			DESCRIPTION
				"The low threshold voltage alarm cleared. The unit is 0.1V. The range is 0-65. Default is 0."
			::= { onuPerformParameterAlarmsSetEntry 24 }

		
		-- 1.1.1.1.25
		voltageAlarmLowLimitRowStatus OBJECT-TYPE
			SYNTAX RowStatus
			ACCESS read-create
			STATUS mandatory
			DESCRIPTION
				"The row status of voltage low alarm."
			::= { onuPerformParameterAlarmsSetEntry 25 }

		
		-- 1.1.2
		onuPerformParameterTable OBJECT-TYPE
			SYNTAX SEQUENCE OF OnuPerformParameterEntry
			ACCESS not-accessible
			STATUS mandatory
			DESCRIPTION
				"Description."
			::= { nmsOnuPerfSet 2 }

		
		-- 1.1.2.1
		onuPerformParameterEntry OBJECT-TYPE
			SYNTAX OnuPerformParameterEntry
			ACCESS not-accessible
			STATUS mandatory
			DESCRIPTION
				"Description."
			INDEX { ifIndex }
			::= { onuPerformParameterTable 1 }

		
		OnuPerformParameterEntry ::=
			SEQUENCE { 
				ifIndex
					INTEGER,
				cpuUsage
					INTEGER,
				ramUsage
					INTEGER,
				temperature
					INTEGER,
				voltage
					INTEGER
			 }

		-- 1.1.2.1.1
		ifIndex OBJECT-TYPE
			SYNTAX INTEGER
			ACCESS read-write
			STATUS mandatory
			DESCRIPTION
				"Index of LLID interface."
			::= { onuPerformParameterEntry 1 }

		
		-- 1.1.2.1.2
		cpuUsage OBJECT-TYPE
			SYNTAX INTEGER (0..100)
			ACCESS read-write
			STATUS mandatory
			DESCRIPTION
				"CPU usage . The unit is 1%. The range is 1-100. Default is 0."
			DEFVAL { 0 }
			::= { onuPerformParameterEntry 2 }

		
		-- 1.1.2.1.3
		ramUsage OBJECT-TYPE
			SYNTAX INTEGER (0..100)
			ACCESS read-write
			STATUS mandatory
			DESCRIPTION
				"RAM usage. The unit is 1%. The range is 1-100. Default is 0."
			DEFVAL { 0 }
			::= { onuPerformParameterEntry 3 }

		
		-- 1.1.2.1.4
		temperature OBJECT-TYPE
			SYNTAX INTEGER (-1280..1280)
			ACCESS read-write
			STATUS mandatory
			DESCRIPTION
				"Temperature.The unit is 0.1 degree. The range is -1280-1280. Default is 0."
			DEFVAL { 0 }
			::= { onuPerformParameterEntry 4 }

		
		-- 1.1.2.1.5
		voltage OBJECT-TYPE
			SYNTAX INTEGER (0..65)
			ACCESS read-write
			STATUS mandatory
			DESCRIPTION
				"Voltage.The unit is 0.1V. The range is 0-65. Default is 0."
			DEFVAL { 0 }
			::= { onuPerformParameterEntry 5 }

		
		-- 1.2
		nmsOnuPerfNotif OBJECT IDENTIFIER ::= { nmsEponOnuTrap 8 }

		
		-- 1.2.1
		paraStatus OBJECT-TYPE
			SYNTAX INTEGER
				{
				above(1),
				below(2),
				normal(3)
				}
			ACCESS read-write
			STATUS mandatory
			DESCRIPTION
				"Description."
			::= { nmsOnuPerfNotif 1 }

		
	
--
-- Trap definitions
--
	
--		onuPerformParameterAlarm TRAP-TYPE 
--			ENTERPRISE nmsOnuPerfNotif
--			VARIABLES { ifIndex, paraStatus, cpuUsage, ramUsage, temperature, 
--				voltage }
--			DESCRIPTION 
--				"Description."
--			::=  2


		
		-- 1.2.0
		nmsOnuPerfNotifV2 OBJECT-IDENTITY
			STATUS current
			DESCRIPTION 
				"Root node for the converted TRAP-TYPEs."
			::= { nmsOnuPerfNotif 2 }

		
		-- 1.2.0.2
		onuPerformParameterAlarm NOTIFICATION-TYPE
			OBJECTS { ifIndex, paraStatus, cpuUsage, ramUsage, temperature, 
				voltage }
			STATUS current
			DESCRIPTION 
				"Description."
			::= { nmsOnuPerfNotifV2 2 }

	
	END

--
-- 
--
